module crlf {
    namespace "urn:crlf";
    prefix crlf;

    list foo {
        unique "a
                b";

        leaf a {
            type string;
        }
        leaf b {
            type string;
        }
    }
}
